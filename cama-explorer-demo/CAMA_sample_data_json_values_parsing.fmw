FME workspace CAMA_sample_data_json_values_parsing.fmw

Parameters:
- SourceDataset_JSON = https://vtopendata-prd.s3.us-east-2.amazonaws.com/_Other/CAMA/sample/Improvements.json   # Source JSON (JavaScript Object Notation) File or URL
- SourceDataset_JSON_5 = https://vtopendata-prd.s3.us-east-2.amazonaws.com/_Other/CAMA/sample/CI_Building.json   # Source JSON (JavaScript Object Notation) File or URL
- SourceDataset_JSON_7 = https://vtopendata-prd.s3.us-east-2.amazonaws.com/_Other/CAMA/sample/Land_Site.json   # Source JSON (JavaScript Object Notation) File or URL
- SourceDataset_JSON_6 = https://vtopendata-prd.s3.us-east-2.amazonaws.com/_Other/CAMA/sample/Land_Detail.json   # Source JSON (JavaScript Object Notation) File or URL

Readers:
- JSON_1: JSON from $(SourceDataset_JSON)
- JSON_2: JSON from $(SourceDataset_JSON_5)
- JSON_3: JSON from $(SourceDataset_JSON_7)
- JSON_4: JSON from $(SourceDataset_JSON_6)

Note: JSONFeature: CI_Building [JSON]
JSONFeature (reader JSON_2)
    attributes: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
Note: JSONFeature: Land_Site [JSON]
JSONFeature (reader JSON_3)
    attributes: Id string, LandHeaderId string, BegEffDate string, EffStatus string, TranId string, LastUpdate string, CategoryType string, CodeType string, RelSize string, PostingSource string
    -> AttributeFilter
AttributeFilter
    ATTR_NAME = CategoryType
    ATTR_VALUES = <Empty>,<Missing>,<Null>,<Unfiltered>,sc_street,sc_util,zoning
    sc_street -> UniqueValueLogger_2
    sc_util -> AttributeFilter_2
    zoning -> UniqueValueLogger_3
    zoning -> AttributeFilter_4
UniqueValueLogger_2
    VAL = @Value(CodeType)
AttributeFilter_2
    ATTR_NAME = CodeType
    ATTR_VALUES = <Empty>,<Missing>,<Null>,<Unfiltered>,all,elect,gas,septic,sewer,water,well
Note: Zoning
UniqueValueLogger_3
    VAL = @Value(CodeType)
Note: Zoning Codes
AttributeFilter_4
    ATTR_NAME = CodeType
    ATTR_VALUES = <Empty>,<Missing>,<Null>,<Unfiltered>,CA,EBC,HC,HDR,I,LDR,MDR,OBR,VHD
    CA -> AttributeCreator
    EBC -> AttributeCreator
    HC -> AttributeCreator
    HDR -> AttributeCreator
    I -> AttributeCreator
    LDR -> AttributeCreator
    MDR -> AttributeCreator
    OBR -> AttributeCreator
    VHD -> AttributeCreator
Note: Barre Town Zoning Codes Lookup per source: https://cms2.revize.com/revize/townofbarrevt/Town%20Plan%2020%20Updated%20091421.pdf
AttributeCreator
    ATTR_TABLE = SET_TO Zoning_Name (varchar(200)) = FME_CONDITIONAL:DEFAULT_VALUE'_FME_NO_OP_'BOOL_OP;OR;COMPOSITE_TEST;1;TEST @Value(CodeType) = CA'Conservation'BOOL_OP;OR;COMPOSITE_TEST;1;TEST @Value(CodeType) = EBC'East Barre Commercial'BOOL_OP;OR;COMPOSITE_TEST;1;TEST @Value(CodeType) = HC'Highway Commercial'BOOL_OP;OR;COMPOSITE_TEST;1;TEST @Value(CodeType) = HDR'High Density Residential'BOOL_OP;OR;COMPOSITE_TEST;1;TEST @Value(CodeType) = I'Industrial'BOOL_OP;OR;COMPOSITE_TEST;1;TEST @Value(CodeType) = LDR'Low Density Residential'BOOL_OP;OR;COMPOSITE_TEST;1;TEST @Value(CodeType) = MDR'Medium Density Residential'BOOL_OP;OR;COMPOSITE_TEST;1;TEST @Value(CodeType) = OBR'Office Building Retail'BOOL_OP;OR;COMPOSITE_TEST;1;TEST @Value(CodeType) = VHD'Very High Density Residential'FME_NUM_CONDITIONS10___
Note: JSONFeature: Land_Detail [JSON]
JSONFeature (reader JSON_4)
    attributes: Id string, LandHeaderId string, LandLineNumber string, UseSequence string, BegEffDate string, EffStatus string, TranId string, LastUpdate string, AppHeaderId string, LandDetailType string, PrimaryUse string, RelMktLine string, LandType string, lcm string, Zoning string, ComIndType string, Topography string, Directional string, ActualFrontage string, EffFrontage string, EffDepth string, LDAcres string, SqrFeet string, UnitCount string, Slope string, SoilIdent string, DistanceToRear string, SiteRating string, BaseRate string, DepthFactor string,
      SmallAcreFactor string, SoilProdFactor string, AdjRate string, ExtValue string, AppdValue string, TableNbhdPriced string, NbhdWhenPriced string, LandModelId string, PostingSource string, ExcessLandFlag string
    -> AttributeFilter_5
Note: LandType values
AttributeFilter_5
    ATTR_NAME = LandType
    ATTR_VALUES = <Empty>,<Missing>,<Null>,<Unfiltered>,AG,CF,CS,CW,CX,DR,FL,FN,FR,HS,MN,PC,PI,PS,PW,QG,RE,RW,SC,SP,SS,UC,WL
    AG -> AttributeCreator_2
    CF -> AttributeCreator_2
    CS -> AttributeCreator_2
    CW -> AttributeCreator_2
    CX -> AttributeCreator_2
    DR -> AttributeCreator_2
    FL -> AttributeCreator_2
    FN -> AttributeCreator_2
    FR -> AttributeCreator_2
    HS -> AttributeCreator_2
    MN -> AttributeCreator_2
    PC -> AttributeCreator_2
    PI -> AttributeCreator_2
    PS -> AttributeCreator_2
    PW -> AttributeCreator_2
    QG -> AttributeCreator_2
    RE -> AttributeCreator_2
    RW -> AttributeCreator_2
    SC -> AttributeCreator_2
    SP -> AttributeCreator_2
    SS -> AttributeCreator_2
    UC -> AttributeCreator_2
    WL -> AttributeCreator_2
AttributeCreator_2
    ATTR_TABLE = SET_TO LandType (buffer) = FME_CONDITIONAL:DEFAULT_VALUE'_FME_NO_OP_'BOOL_OP;OR;COMPOSITE_TEST;1;TEST @Value(LandType) = AG'Current Use - Ag Open Idle'BOOL_OP;OR;COMPOSITE_TEST;1;TEST @Value(LandType) = CF'Current Use - Agricultural'BOOL_OP;OR;COMPOSITE_TEST;1;TEST @Value(LandType) = CS'Commercial Sewer'BOOL_OP;OR;COMPOSITE_TEST;1;TEST @Value(LandType) = CW'Commercial Water Source'BOOL_OP;OR;COMPOSITE_TEST;1;TEST @Value(LandType) = CX'Commercial Excess'BOOL_OP;OR;COMPOSITE_TEST;1;TEST @Value(LandType) = DR'Development Rights'BOOL_OP;OR;COMPOSITE_TEST;1;TEST @Value(LandType) = FL'Farmland'BOOL_OP;OR;COMPOSITE_TEST;1;TEST @Value(LandType) = FN'Current Use - Non Prod Forest'BOOL_OP;OR;COMPOSITE_TEST;1;TEST @Value(LandType) = FR'Current Use - Forest'BOOL_OP;OR;COMPOSITE_TEST;1;TEST @Value(LandType) = HS'Homesite'BOOL_OP;OR;COMPOSITE_TEST;1;TEST @Value(LandType) = MN'Sand & Gravel Pit'BOOL_OP;OR;COMPOSITE_TEST;1;TEST @Value(LandType) = PC'Primary Commercial'BOOL_OP;OR;COMPOSITE_TEST;1;TEST @Value(LandType) = PI'Primary Industrial'BOOL_OP;OR;COMPOSITE_TEST;1;TEST @Value(LandType) = PS'Public Sewer'BOOL_OP;OR;COMPOSITE_TEST;1;TEST @Value(LandType) = PW'Public Water'BOOL_OP;OR;COMPOSITE_TEST;1;TEST @Value(LandType) = QG'Granite Reserve'BOOL_OP;OR;COMPOSITE_TEST;1;TEST @Value(LandType) = RE'Excess Acreage'BOOL_OP;OR;COMPOSITE_TEST;1;TEST @Value(LandType) = RW'Road Right of Way'BOOL_OP;OR;COMPOSITE_TEST;1;TEST @Value(LandType) = SC'Secondary Commercial'BOOL_OP;OR;COMPOSITE_TEST;1;TEST @Value(LandType) = SP'Septic System'BOOL_OP;OR;COMPOSITE_TEST;1;TEST @Value(LandType) = SS'Spring Water Source'BOOL_OP;OR;COMPOSITE_TEST;1;TEST @Value(LandType) = UC'Industrial Excess'BOOL_OP;OR;COMPOSITE_TEST;1;TEST @Value(LandType) = WL'Well'FME_NUM_CONDITIONS24___
Note: JSONFeature: Improvements [JSON]
JSONFeature (reader JSON_1)
    attributes: lrsn string, extension string, dwelling_number string, imp_line_number string, improvement_id string, status string, last_update string, imp_type string, attached_flag string, imp_height string, imp_width string, imp_length string, imp_capacity string, construction_type string, grade string, year_built string, eff_year_built string, year_remodeled string, condition string, imp_base_rate1 string, imp_adj_rate1 string, imp_size string, unit_type string, reproduction_cost1 string, phys_depreciation1 string, ovrride_phys_depr string, obs_depreciation string, funct_depreciation string, pct_complete string, rem_value1 string,
      true_tax_value1 string, imp_eff_perim string, imp_par string, finish_code string, calc_obs_dep string, location_adj1 string, location_adj3 string, sketch_code string, eff_year string, sound_value_code string, bldg_section string, effective_age_calc_flag string, imp_base_rate3 string, imp_adj_rate3 string, reproduction_cost3 string, phys_depreciation3 string, rem_value3 string, true_tax_value3 string, number_items string, import_imp_id string, import_card_number string, misc_imp_type string, import_dwell_id string, ext_cover string, sound_value_reason string, OtherImpFlag string
    -> UniqueValueLogger
Note: Count Unique Values for IMPTYPE
UniqueValueLogger
    VAL = @Value(imp_type)

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = NO
    KEEP_ATTRS = _value
    -> Aggregator
Note: Create aggregates of / features, grouped by / the target attribute value
Aggregator
    ACCUM_ATTRS_NAME = Merge Incoming Attributes
    AGGREGATE_TYPE = Homogeneous Collection (If Possible)
    COUNT_ATTR = _count
    GROUP_BY = _value
    MODE = Geometry - Assemble One Level
    SEP = ,
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
